# Open via FreeCAD's Macro menu; no export/save/geometry approval is performed.
from pathlib import Path
import importlib.util,sys
import FreeCAD as App
import FreeCADGui as Gui
R=Path(__file__).resolve().parent
sys.path.insert(0,str(R.parent/'slide-clips'))
sys.path.insert(0,str(R))
spec=importlib.util.spec_from_file_location('features',R/'features.py')
features=importlib.util.module_from_spec(spec);sys.modules['features']=features;spec.loader.exec_module(features)
d=App.openDocument(str(R/'cad/quarter-turn-case.FCStd'))
for o in d.Objects:
 if isinstance(getattr(o,'Proxy',None),features.Feature):o.touch()
d.recompute()
for o in d.Objects:
 if not hasattr(o,'Shape') or o.TypeId=='App::DocumentObjectGroup':continue
 assert o.Shape.isValid() and o.Shape.isClosed(),o.Name
 o.ViewObject.Visibility=o.Name in ('Base020','Lid020','Key0','Key1')
 if hasattr(o.ViewObject,'ShapeColor'):
  o.ViewObject.ShapeColor=(.38,.61,.73) if 'Base' in o.Name or 'Keeper' in o.Name else ((.75,.80,.85) if 'Lid' in o.Name else (.94,.64,.23))
  o.ViewObject.LineColor=(.14,.20,.28)
  if o.Name.startswith(('PCB','Populated')):o.ViewObject.ShapeColor=(.80,.24,.30)
Gui.activeDocument().activeView().viewAxonometric();Gui.activeDocument().activeView().fitAll()
print('CAD SCREEN / COUPON TEST ONLY. Internal base height49.2; original external shell15.')
print('Toggle Fit020/Fit010/Fit000 and ElectronicsScreens. Original installed PCB stack and printed strength unverified.')
