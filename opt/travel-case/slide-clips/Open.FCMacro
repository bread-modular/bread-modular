# Portable FINAL assembly opener. Run this macro, not the historical concept macro.
import sys
from pathlib import Path
import FreeCAD as App
root=Path(__file__).resolve().parent
sys.path.insert(0,str(root))
import final_features
import clip_features
doc=App.openDocument(str(root/'cad/slide-clips.FCStd'))
for obj in doc.Objects:
    if isinstance(getattr(obj,'Proxy',None),final_features.SlideFeature):obj.touch()
doc.recompute()
for obj in doc.Objects:
    if hasattr(obj,'Shape'):
        assert obj.Shape.isValid() and obj.Shape.isClosed(),obj.Name
if App.GuiUp:
    import FreeCADGui as Gui
    for obj in doc.Objects:
        if hasattr(obj,'ViewObject'):
            obj.ViewObject.Visibility=obj.Name in ('Bottom','Top','ClipA','ClipD')
            if hasattr(obj.ViewObject,'ShapeColor'):
                obj.ViewObject.ShapeColor=(.21,.43,.61) if obj.Name=='Bottom' else (.68,.76,.83) if obj.Name=='Top' else (.99,.48,.08)
                obj.ViewObject.LineColor=(.18,.22,.26)
    Gui.activeDocument().activeView().viewAxonometric()
    Gui.activeDocument().activeView().fitAll()
