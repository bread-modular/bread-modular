# Open the final full assembly with live FeaturePython recipes and useful visibility.
import sys
from pathlib import Path
import FreeCAD as App
root=Path(__file__).resolve().parent
sys.path.insert(0,str(root))
import latch_features
App.openDocument(str(root/'cad/flush-latch.FCStd'))
if App.GuiUp:
    import FreeCADGui as Gui
    doc=App.ActiveDocument
    for o in doc.Objects:
        if hasattr(o,'ViewObject'):
            o.ViewObject.Visibility=o.Name in ('Bottom','Top','Slider1','Slider2','Slider3','Slider4','Gate1','Gate2','Gate3','Gate4')
            if hasattr(o.ViewObject,'ShapeColor'):
                o.ViewObject.ShapeColor=(.19,.42,.61) if o.Name=='Bottom' else (.67,.73,.79) if o.Name=='Top' else (.98,.48,.07) if o.Name.startswith('Slider') else (.28,.65,.38)
    Gui.activeDocument().activeView().viewAxonometric()
    Gui.activeDocument().activeView().fitAll()
